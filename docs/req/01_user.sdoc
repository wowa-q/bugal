[DOCUMENT]
TITLE: Project requirements template
VERSION: 1.0.0
REQ_PREFIX: USER-
OPTIONS:
  REQUIREMENT_STYLE: Table

[GRAMMAR]
ELEMENTS:
- TAG: REQUIREMENT
  FIELDS:
  - TITLE: UID
    TYPE: String
    REQUIRED: False
  - TITLE: STATUS
    TYPE: String
    REQUIRED: True
  - TITLE: VERIFICATION
    TYPE: String
    REQUIRED: True
  - TITLE: TITLE
    TYPE: String
    REQUIRED: False
  - TITLE: STATEMENT
    TYPE: String
    REQUIRED: True
  - TITLE: RATIONALE
    TYPE: String
    REQUIRED: True
  - TITLE: COMMENT
    TYPE: String
    REQUIRED: False
  - TITLE: LAYER
    TYPE: MultipleChoice(config, handler, UI, DB)
    REQUIRED: True
  - TITLE: UNIT
    TYPE: String
    REQUIRED: False
  RELATIONS:
  - TYPE: Parent
  - TYPE: File

[FREETEXT]
Introduction:
This specification describes user interface requirements

[/FREETEXT]

[SECTION]
TITLE: User interface
REQ_PREFIX: USER-

[REQUIREMENT]
UID: USER-1
STATUS: Draft
VERIFICATION: tested
TITLE: Command line interface
STATEMENT: Es soll ein command line interface geben der über bgl.py aufgerufen werden kann.
RATIONALE: Es ist flexiber zu testen und einfacher zu implementieren als gui. Die neuen Funktionen können erst in CLI Mode getestet werden bevor sie in GUI unterstützt werden.
COMMENT: any comment
LAYER: UI

[REQUIREMENT]
UID: USER-2
STATUS: Draft
VERIFICATION: -
TITLE: Grafical user interface
STATEMENT: Es soll eine GUI geben über die der End user seine Aktionen ausführen kann.
RATIONALE: Es ist einfach und intuitiver für die user das Tool über eine GUI zu benutzen.
LAYER: UI

[REQUIREMENT]
UID: USER-3
STATUS: Draft
VERIFICATION: -
TITLE: Cobfiguration
STATEMENT: Das Tool soll über config.toml konfiguriert werden.
RATIONALE: Vereinfacht die Benutzung des Tools.
COMMENT: any comment
LAYER: UI

[REQUIREMENT]
UID: USER-4
STATUS: Draft
VERIFICATION: -
TITLE: Excel export
STATEMENT: Das Tool soll einen export in Excel anbiete.
RATIONALE: Der Usr will seine Daten in Excel weiter verarbeiten.
COMMENT: TBD
LAYER: UI

[REQUIREMENT]
UID: USER-5
STATUS: Draft
VERIFICATION: -
TITLE: Excel import
STATEMENT: Das Tool soll Möglichkeit anbieten Daten aus Excel wieder in die Datenbank zu importieren.
RATIONALE: TBD.
COMMENT: TBD
LAYER: UI

[REQUIREMENT]
UID: USER-6
STATUS: Draft
VERIFICATION: -
TITLE: TEMPLATE
STATEMENT: TBD.
RATIONALE: TBD.
COMMENT: TBD
LAYER: UI

[SECTION]
TITLE: Command line interface
REQ_PREFIX: CLI-

[REQUIREMENT]
UID: CLI-1
STATUS: Draft
VERIFICATION: -
TITLE: Command line interface
STATEMENT: Es soll ein Kommando zum Import csv geben mit Pfadangabe.
RATIONALE: csv needs to be imported
COMMENT: any comment
LAYER: UI
UNIT: cli.py
RELATIONS:
- TYPE: Parent
  VALUE: USER-1

[REQUIREMENT]
UID: CLI-2
STATUS: Draft
VERIFICATION: -
TITLE: Command line interface
STATEMENT: Es soll ein Kommando zum Import csv geben mit Pfadangabe.
RATIONALE: csv needs to be imported
COMMENT: This is a multiline comment.
LAYER: UI
UNIT: cli.py
RELATIONS:
- TYPE: Parent
  VALUE: CLI-1
- TYPE: File
  VALUE: /tests/unit/test_cli.py

[SECTION]
TITLE: Command Line user interface - Tests
REQ_PREFIX: TST-CLI-

[REQUIREMENT]
UID: TST-CLI-1
STATUS: Draft
VERIFICATION: automated
TITLE: Command line interface positive test
STATEMENT: Es soll geprüft werden, dass CLI funktioniert.
RATIONALE: csv needs to be imported
COMMENT: >>>
test_import_single_csv
test_import_banch_of_csv
<<<
LAYER: UI
UNIT: test_cli.py
RELATIONS:
- TYPE: Parent
  VALUE: CLI-1
- TYPE: File
  VALUE: /tests/unit/test_cli.py

[/SECTION]

[/SECTION]

[SECTION]
TITLE: Grafical user interface
REQ_PREFIX: GUI-

[REQUIREMENT]
UID: GUI-1
STATUS: Draft
VERIFICATION: -
TITLE: GUI shall be provided
STATEMENT: Es soll eine GUI geben zum Import csv geben mit Pfadangabe.
RATIONALE: csv needs to be imported
LAYER: UI
UNIT: cli.py

[/SECTION]

[/SECTION]
